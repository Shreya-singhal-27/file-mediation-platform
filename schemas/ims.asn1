CDFModuleImsVoice DEFINITIONS ::= BEGIN
IMSVoiceRecord ::= SET {
cdfId [0] IA5String (SIZE (0..20)) OPTIONAL,
cdrseqnum [1] INTEGER OPTIONAL,
lclrcdseqnum [2] INTEGER OPTIONAL,
rcdseqnum [3] INTEGER OPTIONAL,
calltype [4] INTEGER OPTIONAL,
imschargingid [5] UTF8String (SIZE (0..164)) OPTIONAL,
lrn [6] UTF8String (SIZE (0..10)) OPTIONAL,
callerNumber [7] UTF8String (SIZE (0..32)) OPTIONAL,
calledno [8] UTF8String (SIZE (0..32)) OPTIONAL,
fullcalledno [9] UTF8String (SIZE (0..128)) OPTIONAL,
callarrivaltimestamp [10] OCTET STRING (SIZE (0..20)) OPTIONAL,
callanswertimestamp [11] OCTET STRING (SIZE (0..20)) OPTIONAL,
callendtimestamp [12] OCTET STRING (SIZE (0..20)) OPTIONAL,
duration [13] INTEGER OPTIONAL,
servicereasonreturncode [14] INTEGER OPTIONAL,
serviceinvoke [15] INTEGER OPTIONAL,
associatedpartyaddress[16] UTF8String (SIZE (0..64)) OPTIONAL,
srvcctype [17] INTEGER OPTIONAL,
initialicid [18] UTF8String (SIZE (0..164)) OPTIONAL,
accesstransfertype [19] INTEGER OPTIONAL,
origaccessnetworkinfo [20] OCTET STRING (SIZE (0..164)) OPTIONAL,
termaccessnetworkinfo [21] OCTET STRING (SIZE (0..164)) OPTIONAL,
origincsessionid [22] UTF8String(SIZE (0..164)) OPTIONAL,
termincsessionid [23] UTF8String (SIZE (0..164)) OPTIONAL,
origogsessionid [24] UTF8String (SIZE (0..164)) OPTIONAL,
termogsessionid [25] UTF8String (SIZE (0..164)) OPTIONAL,
origioi [26] UTF8String (SIZE (0..128)) OPTIONAL,
termioi [27] UTF8String (SIZE (0..128)) OPTIONAL,
codecs [28] UTF8String (SIZE (0..64)) OPTIONAL,
mediainitiatorflag [29] INTEGER OPTIONAL,
mediainitiatorparty [30] UTF8String (SIZE (0..64)) OPTIONAL,
scscfinformation [31] UTF8String (SIZE (0..128)) OPTIONAL,
asinformation [32] UTF8String (SIZE (0..128)) OPTIONAL,
imsemergencyindicator [33] INTEGER OPTIONAL,
privateuserid [34] UTF8String (SIZE (0..128)) OPTIONAL ,
origdeviceip [35] OCTET STRING (SIZE (0..32)) OPTIONAL,
termdeviceip [36] OCTET STRING (SIZE (0..32)) OPTIONAL,
numofdiversions [37] INTEGER OPTIONAL,
origcugid [38] UTF8String(SIZE (0..20)) OPTIONAL,
termcugid [39] UTF8String (SIZE (0..20)) OPTIONAL,
resourcepri [40] INTEGER OPTIONAL,
conferenceid [41] UTF8String (SIZE (0..36)) OPTIONAL,
confchangetime [42] OCTET STRING (SIZE (0..20)) OPTIONAL,
confnumparticipants [43] INTEGER OPTIONAL,
confparticipationacttype [44] INTEGER OPTIONAL,
servedIMEI [45] OCTET STRING (SIZE (0..16)) OPTIONAL,
mmtelservicetype [46] INTEGER OPTIONAL,
imsvisitednetworkid [47] UTF8String (SIZE (0..164)) OPTIONAL,
firstcellIdorig [48] OCTET STRING (SIZE (0..30)) OPTIONAL,
lastcellIdorig [49] OCTET STRING (SIZE (0..30)) OPTIONAL,
firstcellIdterm [50] OCTET STRING (SIZE (0..30)) OPTIONAL,
lastcellIdterm [51] OCTET STRING (SIZE (0..30)) OPTIONAL,
cdrtype [52] INTEGER OPTIONAL,
subsPLMN [53] OCTET STRING (SIZE (0..6)) OPTIONAL,
subsIMSI [54] OCTET STRING (SIZE (0..16)) OPTIONAL,
substype [55] INTEGER OPTIONAL,
recordOpeningTime [56] OCTET STRING (SIZE (0..20)) OPTIONAL,
recordClosingTime [57] OCTET STRING (SIZE (0..20)) OPTIONAL,
termservedIMEI [58] OCTET STRING (SIZE (0..164)) OPTIONAL,
termsubsPLMN [59] OCTET STRING (SIZE (0..164)) OPTIONAL,
termsubsIMSI [60] OCTET STRING (SIZE (0..164)) OPTIONAL,
callinggt [61] OCTET STRING (SIZE (0..164)) OPTIONAL,
callrefernum [62] OCTET STRING (SIZE (0..164)) OPTIONAL,
ringingtimestamp [63] OCTET STRING (SIZE (0..164)) OPTIONAL,
dummy7 [64] OCTET STRING (SIZE (0..164)) OPTIONAL,
termsubstype [65] INTEGER OPTIONAL,
servicekey [66] INTEGER OPTIONAL,
rattype [67] INTEGER OPTIONAL,
audioduration [68] INTEGER OPTIONAL,
videoduration [69] INTEGER OPTIONAL,
dummy13 [70] INTEGER OPTIONAL,
dummy14 [71] INTEGER OPTIONAL,
dummy15 [72] OCTET STRING (SIZE (0..164)) OPTIONAL,
dummy16 [73] INTEGER OPTIONAL,
termnetworkid [74] UTF8String (SIZE (0..164)) OPTIONAL,
termscscfinformation [75] UTF8String (SIZE (0..164)) OPTIONAL,
termasinformation [76] UTF8String (SIZE (0..164)) OPTIONAL,
termcodec [77] UTF8String (SIZE (0..164)) OPTIONAL,
confcalledstr [78] UTF8String (SIZE (0..164)) OPTIONAL
}
END
